;;
;; K59C0.LSP
;; Copyright (C) 1996 by Luiz Marcio F A Viana, 3/18/96.
;;

;;
;; DBLSCR: duplica a area da tela utilizando o comando vports
;;

(defun c:dblscr(/ p1 p2 p3 p4)
  (setq oldech (getvar "cmdecho"))
  (setvar "cmdecho" 0)

  (prompt "\nSelect first window...")
  (initget 1)
  (setq p1 (getpoint "\nFirst corner: "))
  (initget 1)
  (setq p2 (getcorner p1 "\nSecond corner: "))

  (prompt "\nSelect second window...")
  (initget 1)
  (setq p3 (getpoint "\nFirst corner: "))
  (initget 1)
  (setq p4 (getcorner p3 "\nSecond corner: "))

  (command
    ".view" "s" "$view"
    ".vports" "2" "h"
  ) ; end command
  (setvar "cvport" 2)
  (command ".zoom" "w" p1 p2)
  (setvar "cvport" 3)
  (command ".zoom" "w" p3 p4)
  (setvar "cvport" 2)

  (setvar "cmdecho" oldech)
  (princ)
) ; end defun

;;
;; SISCR: retorna ao estado original uma vports ativa
;;

(defun c:siscr()
  (setq oldech (getvar "cmdecho"))
  (setvar "cmdecho" 0)
  (command ".vports" "si")
  (command ".view" "r" "$view" "y")
  (setvar "cmdecho" oldech)
  (princ)
) ; end defun

(princ)
