;From CADENCE Magazine January, 1990
;Page 93

(DEFUN C:ATTEXPLD ()
  (m:savevars)

 (SETQ ERRORXY NIL)
 (PRINC "\nSELECT BLOCKS")
 (IF (SETQ SS1 (SSGET))
  (PROGN
   (SETQ N -1)
   (WHILE (SETQ ENAME1 (SSNAME SS1 (SETQ N (1+ N))))
    (IF
     (AND (= (CDR (ASSOC 0 (ENTGET ENAME1))) "INSERT")
          (= (CDR (ASSOC 41 (ENTGET ENAME1)))(CDR (ASSOC 42 (ENTGET 
ENAME1)))))
     (PROGN
      (IF (/= (ASSOC 66 (ENTGET ENAME1)) NIL)
       (PROGN
        (WHILE (/= (CDR (ASSOC 0 (ENTGET (SETQ ENAME1 (ENTNEXT 
ENAME1)))))"SEQEND")
         (IF (= (CDR (ASSOC 0 (SETQ ENT1 (ENTGET ENAME1)))) "ATTRIB")
          (PROGN
           (SETQ VALUE1 (CDR (ASSOC 1 ENT1))  STYLE1 (CDR (ASSOC 7 
ENT1)))
           (SETQ LAYER1 (CDR (ASSOC 8 ENT1))  HIGHT1 (CDR (ASSOC 40 
ENT1)))
           (SETQ WIDTH1 (CDR (ASSOC 41 ENT1)))
           (IF (/= (ASSOC 62 ENT1) NIL)
            (SETQ COLOR1 (CDR (ASSOC 62 ENT1)))(SETQ COLOR1 NIL))
           (SETQ JUSTF1 (CDR (ASSOC 72 ENT1))  INSPT1 (CDR (ASSOC 
10 ENT1)))
           (IF (AND
            (/= (ASSOC 11 ENT1) NIL)(/= JUSTF1 0)(/= JUSTF1 3)(/= 
JUSTF1 5))
            (SETQ INSPT1 (CDR (ASSOC 11 ENT1))))
           (SETQ ROTAN1 (RTD (CDR (ASSOC 50 ENT1))))
           (IF (= JUSTF1 1) (SETQ JUSTF1 "C"))
           (IF (= JUSTF1 2) (SETQ JUSTF1 "R"))
           (IF (= JUSTF1 4) (SETQ JUSTF1 "M"))
           (IF (= (CDR (ASSOC 40 (TBLSEARCH "STYLE" STYLE1))) 0)
           (IF (OR (= JUSTF1 0) (= JUSTF1 3) (= JUSTF1 5))
            (COMMAND "TEXT" "S" STYLE1 INSPT1 HIGHT1 ROTAN1 
VALUE1)
            (COMMAND "TEXT" "S" STYLE1 JUSTF1 INSPT1 HIGHT1 ROTAN1 
VALUE1))
           (PROGN
            (IF (OR (= JUSTF1 0) (= JUSTF1 3) (= JUSTF1 5))
             (COMMAND "TEXT" "S" STYLE1 INSPT1 ROTAN1 VALUE1)
             (COMMAND "TEXT" "S" STYLE1 JUSTF1 INSPT1 ROTAN1 
VALUE1))
            (ENTMOD (SUBST (CONS 40 HIGHT1)(ASSOC 40 (ENTGET 
(ENTLAST)))
             (ENTGET (ENTLAST))))))
        (ENTMOD (SUBST (CONS 41 WIDTH1)(ASSOC 41 (ENTGET 
(ENTLAST)))
         (ENTGET (ENTLAST))))
       (ENTMOD (SUBST (CONS 8 LAYER1)(ASSOC 8 (ENTGET (ENTLAST)))
        (ENTGET (ENTLAST))))
    (IF COLOR1 (COMMAND "CHANGE" (ENTLAST) "" "P" "C" COLOR1 "")))))
   (SETQ LASTENT1 (ENTLAST))
   (COMMAND "EXPLODE" (CDR (ASSOC -2 (ENTGET ENAME1))))
   (SETQ EXPENT1 (ENTNEXT LASTENT1))
   (WHILE EXPENT1
    (IF (= (CDR (ASSOC 0 (ENTGET EXPENT1))) "ATTDEF") (ENTDEL 
EXPENT1))
    (SETQ EXPENT1 (ENTNEXT EXPENT1))))
  (COMMAND "EXPLODE" ENAME1)))
 (PROGN
  (IF (= (CDR (ASSOC 0 (ENTGET ENAME1))) "INSERT")
   (IF ERRORXY (SETQ ERRORXY (CONS (CDR (ASSOC 2 (ENTGET 
ENAME1))) ERRORXY))
  (SETQ ERRORXY (LIST (CDR (ASSOC 2 (ENTGET ENAME1))))))))))
 (REDRAW)))
 (IF ERRORXY
  (PROGN (TEXTSCR) (REPEAT 20 (TERPRI))
  (PRINC "\nWARNING - THE FOLLOWING BLOCKS WERE NOT EXPLODED: 
")
  (FOREACH N ERRORXY (PRINC (STRCAT "\n          " N)))
  (TERPRI)
  (PRINC "\n          CAUSE:  X-Y COORDINATES WERE NOT EQUAL\n")))
  (m:restorevars)
(PRINC))

(PRINC)
