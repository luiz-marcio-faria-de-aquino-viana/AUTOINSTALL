; K18c0/Quadro - Abr/91

(defun c:Quadro(/ a1 a2 p1 l1 l2 t1 n1 n2 c15 c75 l4 l2 l9 xm ym x1 y1 m1 m2) 
  (m:savevars)

  (setvar "PICKBOX" 1)
  (setq A1 (getstring T "\nNome do quadro: "))
  (setq P1 (getpoint "\nPonto inicial: "))
  (setq L1 (getint "\nQtd. lampadas: "))
  (setq T1 (getint "\nQtd.  tomadas: "))
  (setq N1 (getint "\nQtd. circuitos: "))
  (setq C15 (* 15.0 (#SCL)))
  (setq C75 (* 7.5 (#SCL)))
  (setq L4 (* 4.0 (#SCL)))
  (setq L2 (* 1.5 (#SCL)))
  (setq L9 (* 9.0 (#SCL)))
  (setq XM (+ (* 120.0 (#SCL)) (* C15 L1) (* C15 T1)))
  (setq YM (+ (* 38.0 (#SCL)) (* L4 N1)))
  (setq X1 (car P1))
  (setq Y1 (cadr P1))
  (setq M1 (list (+ X1 XM) Y1))
  (command "LINE" P1 M1 "")
  (setq M1 (list X1 (+ Y1 C75)))
  (setq M2 (list (+ X1 XM) (+ Y1 C75)))
  (command "LINE" M1 M2 "")
  (setq M1 (list X1 (+ Y1 C75 (* N1 L4))))
  (setq M2 (list (+ X1 XM) (+ Y1 C75 (* N1 L4))))
  (command "LINE" M1 M2 "")
  (setq M1 (list X1 (- (+ Y1 YM) (* 8 (#SCL)))))
  (setq M2 (list (+ X1 XM) (cadr M1)))
  (command "LINE" M1 M2 "")
  (setq M1 (list X1 (+ Y1 YM)))
  (setq M2 (list (+ X1 XM) (+ Y1 YM)))
  (command "LINE" M1 M2 "")
  (command "LINE" M1 P1 "")
  (setq M1 (list (+ X1 XM) Y1))
  (command "LINE" M2 M1 "")
  (setq N2 1)
  (while (<= N2 (+ L1 T1 7))
  	(setq M1 (list (+ X1 (* C15 N2)) Y1))
  	(setq M2 (list (car M1) (+ Y1 (- YM (* 8.0 (#SCL))))))
  	(command "LINE" M1 M2 "")
  	(setq N2 (+ N2 1))
  )
  (setq M1 (list (+ (* 30.0 (#SCL)) (* C15 L1) (* C15 T1) X1) (+ Y1 (- YM (* 18.0 (#SCL))))))
  (setq M2 (list (+ (* 30.0 (#SCL)) (car M1)) (cadr M1)))
  (command "LINE" M1 M2 "")
  (setq M1 (list (+ C75 (car M1)) (cadr M1)))
  (setq M2 (list (+ C75 (car M1)) (+ (* 5.0 (#SCL)) (cadr M1))))
  (command "TRIM" M1 "" M2 "")
  (if (> L1 1) (progn
  		(setq M1 (list (+ X1 C15) (+ Y1 (- YM (* 18.0 (#SCL))))))
  		(setq M2 (list (+ X1 (* C15 (+ L1 1))) (cadr M1)))
  		(command "LINE" M1 M2 "")
  		(setq M1 (list (+ C75 (car M1)) (cadr M1)))
  		(setq N2 1)
  		(while (< N2 L1)
  			(setq M2 (list (+ C15 X1 (* C15 N2)) (+ Y1 (- YM (* 13.0 (#SCL))))))
  			(command "TRIM" M1 "" M2 "")
  			(setq N2 (+ 1 N2))
  			)
  		))
  (if (> T1 1) (progn
  		(setq M1 (list (+ X1 C15 (* C15 L1)) (+ Y1 (- YM (* 18.0 (#SCL))))))
  		(setq M2 (list (+ (car M1) (* C15 T1)) (cadr M1)))
  		(command "LINE" M1 M2 "")
  		(setq M1 (list (+ C75 (car M1)) (cadr M1)))
  		(setq N2 1)
  		(while (< N2 T1)
  			(setq M2 (list (+ C15 X1 (* C15 N2) (* C15 L1)) (+ Y1 (- YM (* 13 (#SCL))))))
  			(command "TRIM" M1 "" M2 "")
  			(setq N2 (+ 1 N2))
  			)
  		))
  (setq N2 1)
  (while (< N2 N1)
  	(setq M1 (list X1 (+ Y1 C75 (* L4 N2))))
  	(setq M2 (list (+ X1 XM) (cadr M1)))
  	(command "LINE" M1 M2 "")
  	(setq N2 (+ N2 1))
  )
  (setq M1 (list (+ X1 (/ XM 2)) (+ Y1 (- YM (* 6.0 (#SCL))))))
  (command "TEXT" "C" M1 (* 3.0 (#SCL)) 0 A1)
  (setq M1 (list (+ X1 C75) (+ Y1 (- YM (* 15.0 (#SCL))))))
  (command "TEXT" "C" M1 L2 0 "NUMERO")
  (command "TEXT" "" "DO")
  (command "TEXT" "" "CIRCUITO")
  (setq M1 (list (+ X1 (/ (* C15 L1) 2) C15) (cadr M1)))
  (if (> L1 1) (setq A1 "LAMPADAS") (setq A1 "LAMPADA"))
  (if (> L1 0) (command "TEXT" "C" M1 L2 0 A1))
  (setq M1 (list (+ X1 C15 (* C15 L1) (/ (* C15 T1) 2)) (cadr M1)))
  (if (> T1 1) (setq A1 "TOMADAS") (setq A1 "TOMADA"))
  (if (> T1 0) (command "TEXT" "C" M1 L2 0 A1))
  (setq M1 (list (+ X1 (* 22.5 (#SCL)) (* (+ L1 T1) C15)) (cadr M1)))
  (command "TEXT" "C" M1 L2 0 "TOTAL")
  (command "TEXT" "" "DE")
  (command "TEXT" "" "PONTOS")
  (setq M1 (list (+ C15 (car M1)) (- (cadr M1) L9)))
  (command "TEXT" "C" M1 L2 0 "(VA)")
  (setq M1 (list (+ C75 (car M1)) (+ (cadr M1) L9)))
  (command "TEXT" "C" M1 L2 0 "POTENCIA")
  (setq M1 (list (+ C75 (car M1)) (- (cadr M1) L9)))
  (command "TEXT" "C" M1 L2 0 "(CV)")
  (setq M1 (list (+ C15 (car M1)) (+ (cadr M1) L9)))
  (command "TEXT" "C" M1 L2 0 "TENSAO")
  (setq M1 (list (car M1) (- (cadr M1) L9)))
  (command "TEXT" "C" M1 L2 0 "(V)")
  (setq M1 (list (+ C15 (car M1)) (+ (cadr M1) L9)))
  (setvar "PICKBOX" 3)
  (command "TEXT" "C" M1 L2 0 "PROTECAO")
  (setq M1 (list (car M1) (- (cadr M1) L9)))
  (command "TEXT" "C" M1 L2 0 "(A)")
  (setq M1 (list (+ C15 (car M1)) (+ (cadr M1) L9)))
  (command "TEXT" "C" M1 L2 0 "BITOLA DO")
  (command "TEXT" "" "CONDUTOR")
  (setq M1 (list (car M1) (- (cadr M1) L9)))
  (command "TEXT" "C" M1 L2 0 "(mm2)")
  (setq M1 (list (+ C15 (car M1)) (+ (cadr M1) L9)))
  (command "TEXT" "C" M1 L2 0 "FASE")
  (setq M1 (list (+ X1 C75) (+ Y1 (* 4.0 (#SCL)))))
  (command "TEXT" "M" M1 L2 0 "TOTAL")
  (setq N2 1)
  (while (<= N2 (+ L1 T1))
  	(setq M1 (list (+ X1 C75 (* N2 C15)) (+ Y1 (- YM (* 24.0 (#SCL))))))
  	(if (<= N2 L1) (setq A1 "Carga da lampada: ") (setq A1 "Carga da tomada: "))
  	(prompt A1)
  	(setq A2 (getstring T))
  	(command "TEXT" "C" M1 L2 0 A2)
  	(setq N2 (+ N2 1))
  )
  (m:restorevars)
  (princ)
);enddefun
